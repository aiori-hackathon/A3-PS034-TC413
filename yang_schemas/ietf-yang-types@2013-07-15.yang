module ietf-yang-types {
  yang-version 1.1;
  namespace "urn:ietf:params:xml:ns:yang:ietf-yang-types";
  prefix yang;

  organization
    "IETF NETMOD (Network Modeling) Working Group";
  contact
    "WG Web:   <https://datatracker.ietf.org/wg/netmod/>
     WG List:  <mailto:netmod@ietf.org>";
  description
    "This module contains a collection of commonly used YANG data types.";

  revision 2013-07-15 {
    description
      "Standard types definition.";
    reference
      "RFC 6991: Common YANG Data Types";
  }

  typedef counter32 {
    type uint32;
    description
      "A non-negative 32-bit integer that monotonically increases.";
  }

  typedef counter64 {
    type uint64;
    description
      "A non-negative 64-bit integer that monotonically increases.";
  }

  typedef gauge32 {
    type uint32;
    description
      "A non-negative 32-bit integer that can increase or decrease.";
  }

  typedef timestamp {
    type string {
      pattern '\d{4}-\d{2}-\d{2}T\d{2}:\d{2}:\d{2}(\.\d+)?(Z|[+-]\d{2}:\d{2})';
    }
    description
      "An ISO 8601 date and time timestamp.";
  }
}
